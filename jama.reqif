Generated complex Jama ReqIF test sample

# Specification: Jama Spec

## REQ-JA1
- Authentication Module
- The authentication module shall validate credentials.
- High
- Security
- Critical component
- Stakeholder Meeting
- Auth-Core

### REQ-JA2
- Password Strength Enforcement
- Password shall comply with strength rules.
- Medium
- Functional
- Check NIST rules
- Security Team
- Auth-Password
- links to -> REQ-JA1

### REQ-JA3
- Account Lockout
- Lock the user account after repeated failures.
- High
- Security
- Align with policy XYZ.
- Audit Team
- Auth-Lockout
- links to -> REQ-JA1
