Extended OMG ReqIF 1.0 Test File with Nested Requirements

# Specification: Vehicle Requirements

## REQ-1: Brake System Response
The brake system shall respond within 100ms of pedal actuation.
- Estimated Effort: 5
- Critical: true

## REQ-1.1: Brake Pedal Sensor Accuracy
The brake pedal sensor shall detect pedal position with ±1mm accuracy.
- Estimated Effort: 3
- Critical: true

## REQ-2: Steering Control Accuracy
The steering shall respond accurately within 50ms delay.
- Estimated Effort: 8
- Critical: false

## REQ-2.1: Steering Angle Sensor Precision
The steering angle sensor shall provide precision within ±0.5 degrees.
- Estimated Effort: 4
- Critical: false
