# System Requirements Example

## REQ-001
- The system shall power on within 2 seconds of ignition.

## REQ-002

## REQ-003
- The system shall support diagnostic communication over CAN according to UDS.

## REQ-004
