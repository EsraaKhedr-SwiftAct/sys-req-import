Generated complex Polarion ReqIF sample

# Specification: Polarion Import/Export Specification

## REQ-A1
- Project shall support data import
- The Polarion project shall allow importing work items from external CSV files.
- High

### REQ-A2
- Project shall allow data export
- The system shall export work items in ReqIF and PDF formats.
- Medium
- links to -> REQ-A1

### REQ-A3
- System shall track import errors
- The system shall log any import failures with detailed messages.
- Low
