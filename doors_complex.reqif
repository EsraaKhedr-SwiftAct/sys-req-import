Generated complex DOORS Next sample

# Specification: Login Specification

## REQ-001: System shall allow user login
The system shall support user login with username and password.
- Status: Draft

### REQ-002: System shall log failed login attempts
The system shall log every failed login attempt for auditing purposes.
- Status: Approved

### REQ-003: System shall lock account after 5 failed logins
If a user fails to login 5 times, the account shall be locked for 10 minutes.
- Status: Draft
- links to -> REQ-001
